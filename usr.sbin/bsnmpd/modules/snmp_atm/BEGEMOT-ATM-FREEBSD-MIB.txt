--
-- Copyright (c) 2004
--	Hartmut Brandt.
-- 	All rights reserved.
--
-- Author: Hartmut Brandt <harti@freebsd.org>
--
-- Redistribution and use in source and binary forms, with or without
-- modification, are permitted provided that the following conditions
-- are met:
-- 1. Redistributions of source code must retain the above copyright
--    notice, this list of conditions and the following disclaimer.
-- 2. Redistributions in binary form must reproduce the above copyright
--    notice, this list of conditions and the following disclaimer in the
--    documentation and/or other materials provided with the distribution.
--
-- THIS SOFTWARE IS PROVIDED BY AUTHOR AND CONTRIBUTORS ``AS IS'' AND
-- ANY EXPRESS OR IMPLIED WARRANTIES, INCLUDING, BUT NOT LIMITED TO, THE
-- IMPLIED WARRANTIES OF MERCHANTABILITY AND FITNESS FOR A PARTICULAR PURPOSE
-- ARE DISCLAIMED.  IN NO EVENT SHALL AUTHOR OR CONTRIBUTORS BE LIABLE
-- FOR ANY DIRECT, INDIRECT, INCIDENTAL, SPECIAL, EXEMPLARY, OR CONSEQUENTIAL
-- DAMAGES (INCLUDING, BUT NOT LIMITED TO, PROCUREMENT OF SUBSTITUTE GOODS
-- OR SERVICES; LOSS OF USE, DATA, OR PROFITS; OR BUSINESS INTERRUPTION)
-- HOWEVER CAUSED AND ON ANY THEORY OF LIABILITY, WHETHER IN CONTRACT, STRICT
-- LIABILITY, OR TORT (INCLUDING NEGLIGENCE OR OTHERWISE) ARISING IN ANY WAY
-- OUT OF THE USE OF THIS SOFTWARE, EVEN IF ADVISED OF THE POSSIBILITY OF
-- SUCH DAMAGE.
--
-- $FreeBSD: releng/11.3/usr.sbin/bsnmpd/modules/snmp_atm/BEGEMOT-ATM-FREEBSD-MIB.txt 312258 2017-01-16 06:55:11Z ngie $
--
-- Private Begemot MIB for ATM interfaces on FreeBSD
--
BEGEMOT-ATM-FREEBSD-MIB DEFINITIONS ::= BEGIN

IMPORTS
    MODULE-IDENTITY, OBJECT-TYPE
	FROM SNMPv2-SMI
    NgNodeIdOrZero
	FROM BEGEMOT-NETGRAPH-MIB
    begemotAtmSysGroup, begemotAtmIfEntry
	FROM BEGEMOT-ATM-MIB;

begemotAtmFreeBSDGroup MODULE-IDENTITY
    LAST-UPDATED "200408060000Z"
    ORGANIZATION "German Aerospace Centre"
    CONTACT-INFO
	    "		Hartmut Brandt

             Postal:    German Aerospace Centre (DLR)
                        Institute of Communications and Navigation
                        82234 Wessling
                        Germany

	     Fax:	+49 8153 28 2844

	     E-mail:	harti@freebsd.org"
    DESCRIPTION
	    "The FreeBSD specific Begemot MIB for ATM interfaces."
    REVISION "200408060000Z"
    DESCRIPTION
	    "Initial revision."
    ::= { begemotAtmSysGroup 1 }

-- Netgraph
begemotAtmNgGroup	OBJECT IDENTIFIER ::= { begemotAtmFreeBSDGroup 1 }

--
-- Interfaces table
--
begemotAtmNgIfTable OBJECT-TYPE
    SYNTAX	SEQUENCE OF BegemotAtmNgIfEntry
    MAX-ACCESS	not-accessible
    STATUS	current
    DESCRIPTION
	    "This table contains an entry for each hardware ATM
	    interface. The table is indexed by the interface index."
    ::= { begemotAtmNgGroup 1 }

begemotAtmNgIfEntry OBJECT-TYPE
    SYNTAX	BegemotAtmNgIfEntry
    MAX-ACCESS	not-accessible
    STATUS	current
    DESCRIPTION
	    "This is a table entry describing one ATM hardware interface."
    AUGMENTS	{ begemotAtmIfEntry }
    ::= { begemotAtmNgIfTable 1 }

BegemotAtmNgIfEntry ::= SEQUENCE {
    begemotAtmNgIfNodeId	NgNodeIdOrZero
}

begemotAtmNgIfNodeId OBJECT-TYPE
    SYNTAX	NgNodeIdOrZero
    MAX-ACCESS	read-only
    STATUS	current
    DESCRIPTION
	    "The netgraph node id of the interface. If there is no
	    node corresponding to the interface, this is 0."
    ::= { begemotAtmNgIfEntry 1 }

END
